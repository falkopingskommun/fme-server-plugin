FME workspace FME workspace example.fmw

Parameters:
- DestinationFormat =
- GENERIC_OUT_BASE_NAME_GENERIC =
- extent =
- layer =

Writers:
- GENERIC_1: GENERIC to C:/ProgramData/Safe Software/FME Server//resources/system/temp/engineresults in EPSG:3010

Note: Create bounding box from extent
Creator
    COORDS = $(extent)
    COORDSYS = EPSG:3010
    GEOMTYPE = 2D Min/Max Box
    NUM = 1
    CREATED -> Junction
    CREATED -> AttributeCreator
Junction
    -> Clipper [CLIPPER]
AttributeCreator
    ATTR_TABLE = SET_TO _layer = $(layer)
    -> AttributeSplitter
AttributeSplitter
    ATTR_NAME = _layer
    DELIMITER = " "
    DROP_EMPTY_PARTS = No
    LIST_NAME = _layer
    TRIM_OPTION = Both
    -> ListExploder
ListExploder
    ATTR_ACCUM_MODE = Merge List Attributes
    ATTR_CONFLICT_RES = Use List Attribute Values
    INDEX_ATTR = _element_index
    LIST_ATTR = _layer{}
    ELEMENTS -> Tester
Note: Check for Origo Multiple layers filter
Tester
    BOOL_OP = OR
    COMPOSITE_TEST = 1
    TEST_CLAUSE = CASE_INSENSITIVE_TEST @Value(_layer) CONTAINS __
    TEST_MODE = CASE_INSENSITIVE_TEST
    PASSED -> StringReplacer
    FAILED -> WFS [INITIATOR]
StringReplacer
    CASE = NO
    FIND_TEXT = \__.*$
    NO_MATCH = _FME_NO_OP_
    REGEXP = YES
    SRC_ATTRS = _layer
    -> DuplicateFilter
DuplicateFilter
    INPUT_ORDERED_CHOICE = No
    KEYATTR = _layer
    UNIQUE -> WFS [INITIATOR]
Note: URL to Geoserver or equivalent
WFS: FeatureReader
    ATTR_ACCUM_MODE = Only Use Result
    COMBINE_GEOM = Use Result
    DATASET = http://..../geoserver/wfs
    FEATURETYPES = @Value(_layer)
    FORMAT = WFS
    INTERACT = NONE
    OUTPUT_FEATURES_DISPLAY = Schema and Data Features
    WFS_CONNECTION_TIMEOUT = 90
    WFS_DISABLE_AUTOMATIC_READER_TYPE_SELECTION = NO
    WFS_DISABLE_XML_NAMESPACE_PROCESSING = NO
    WFS_ENFORCE_PATH_CONTINUITY_BY = SNAPPING_END_POINTS
    WFS_FLATTEN_XML_FRAGMENTS = NO
    WFS_IGNORE_APPLICATON_SCHEMA = no
    WFS_IGNORE_GETFEATURE_ERROR = No
    WFS_LOCAL_CACHE_EXPIRY = 60
    WFS_MAP_COMPLEX_PROPERTIES_AS = Nested Attributes
    WFS_MAP_COVERAGES_AS_FEATURE_TYPES = NO
    WFS_MAP_EMBEDDED_OBJECTS_AS = ATTRIBUTES
    WFS_MAP_GEOMETRY_COLUMNS = YES
    WFS_MAP_PREDEFINED_GML_PROPERTIES = NO
    WFS_MAX_RESULT_FEATURES = 30000000
    WFS_NETWORK_AUTHENTICATION = AUTH_INFO_GROUP,NO,AUTH_METHOD,<Unused>,NAMED_CONNECTION,<Unused>,AUTH_USERNAME,<Unused>,AUTH_PASSWORD,<Unused>
    WFS_PREFERRED_VERSION = 1.1.0
    WFS_PREFER_DATASET_URL = No
    WFS_PREFER_POST = No
    WFS_TRANSFER_TIMEOUT = 90
    WFS_USE_OLD_READER = NO
    WFS_USE_SEARCH_ENVELOPE = NO
    WFS_XML_FRAGMENTS_AS_DOCUMENTS = YES
    <OTHER> -> Clipper [CLIPPEE]
Clipper
    BOUNDARY_CASES = Treat as Inside
    CLEANING_TOLERANCE = None
    CLIP_TYPE = Single Clipper
    LINES_AS_SEGMENTS = No
    MEASURE_TYPE = Continuous
    MISSING_VAL_MODE = Compute
    PRESERVE_CLIPPEE_EXTENTS = No
    VAL_SOURCE = Clippee Only
    INSIDE -> DYNAMIC (writer GENERIC_1)
Note: This writer feature type's Dynamic Parameters are / configured so that at run time the feature type's / schema is determined from the source file.
DYNAMIC (writer GENERIC_1)
